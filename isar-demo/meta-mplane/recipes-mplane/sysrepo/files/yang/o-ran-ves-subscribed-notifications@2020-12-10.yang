module o-ran-ves-subscribed-notifications {
  yang-version 1.1;
  namespace "urn:o-ran:ves-sn:1.0";
  prefix o-ran-vsn;

  import ietf-subscribed-notifications {
    prefix sn;
  }
  import ietf-inet-types {
    prefix inet;
  }

  organization
    "O-RAN Alliance";
  contact
    "www.o-ran.org";
  description
    "This module defines augmentations to ietf-subscribed-notifications to
     enable support of configured notifications sent using VNF Event Stream
     notifications.

     Copyright 2020 the O-RAN Alliance.

     THIS SOFTWARE IS PROVIDED BY THE COPYRIGHT HOLDERS AND CONTRIBUTORS 'AS IS'
     AND ANY EXPRESS OR IMPLIED WARRANTIES, INCLUDING, BUT NOT LIMITED TO, THE
     IMPLIED WARRANTIES OF MERCHANTABILITY AND FITNESS FOR A PARTICULAR PURPOSE
     ARE DISCLAIMED. IN NO EVENT SHALL THE COPYRIGHT HOLDER OR CONTRIBUTORS BE
     LIABLE FOR ANY DIRECT, INDIRECT, INCIDENTAL, SPECIAL, EXEMPLARY, OR
     CONSEQUENTIAL DAMAGES (INCLUDING, BUT NOT LIMITED TO, PROCUREMENT OF
     SUBSTITUTE GOODS OR SERVICES; LOSS OF USE, DATA, OR PROFITS; OR BUSINESS
     INTERRUPTION) HOWEVER CAUSED AND ON ANY THEORY OF LIABILITY, WHETHER IN
     CONTRACT, STRICT LIABILITY, OR TORT (INCLUDING NEGLIGENCE OR OTHERWISE)
     ARISING IN ANY WAY OUT OF THE USE OF THIS SOFTWARE, EVEN IF ADVISED OF THE
     POSSIBILITY OF SUCH DAMAGE.

     Redistribution and use in source and binary forms, with or without
     modification, are permitted provided that the following conditions are met:

     * Redistributions of source code must retain the above copyright notice,
     this list of conditions and the above disclaimer.
     * Redistributions in binary form must reproduce the above copyright notice,
     this list of conditions and the above disclaimer in the documentation
     and/or other materials provided with the distribution.
     * Neither the Members of the O-RAN Alliance nor the names of its
     contributors may be used to endorse or promote products derived from
     this software without specific prior written permission.";

  revision 2020-12-10 {
    description
      "version 5.0.0

       1) initial version";
    reference
      "ORAN-WG4.M.0-v05.00";
  }

  identity o-ran-ves-connectionless {
    base sn:transport;
    description
      "A transport type used to indicate that notifications should be sent using an
       ONAP VES Notification using RESTful connectionless transport";
  }

  grouping event-collector {
    description
      "Provides a reusable description of an event-collector.";
    leaf notification-recipient {
      type inet:uri;
      mandatory true;
      description
        "This URI specifies the address of the notification receiver
         HTTPS endpoint. Additional path elements may be added as required by the
         protocol, i. e. it configures the server root.
         E.g. https://myserver.mydomain.com:8443/notifications.";
    }
  }

  augment "/sn:subscriptions/sn:subscription/sn:receivers/sn:receiver" {
    when "(derived-from-or-self(../../sn:transport, 'o-ran-vsn:o-ran-ves-connectionless'))";
    description
      "This augmentation allows VES-specific receiver parameters to be
       configured.";
    uses event-collector;
  }
}
