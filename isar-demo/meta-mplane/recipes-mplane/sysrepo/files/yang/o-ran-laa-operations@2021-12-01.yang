module o-ran-laa-operations {
  yang-version 1.1;
  namespace "urn:o-ran:laa-operations:1.0";
  prefix o-ran-laa-operations;

  import o-ran-module-cap {
    prefix mcap;
  }

  organization
    "O-RAN Alliance";
  contact
    "www.o-ran.org";
  description
    "This module defines the operations for DFS measurement.

     Copyright 2021 the O-RAN Alliance.

     THIS SOFTWARE IS PROVIDED BY THE COPYRIGHT HOLDERS AND CONTRIBUTORS 'AS IS'
     AND ANY EXPRESS OR IMPLIED WARRANTIES, INCLUDING, BUT NOT LIMITED TO, THE
     IMPLIED WARRANTIES OF MERCHANTABILITY AND FITNESS FOR A PARTICULAR PURPOSE
     ARE DISCLAIMED. IN NO EVENT SHALL THE COPYRIGHT HOLDER OR CONTRIBUTORS BE
     LIABLE FOR ANY DIRECT, INDIRECT, INCIDENTAL, SPECIAL, EXEMPLARY, OR
     CONSEQUENTIAL DAMAGES (INCLUDING, BUT NOT LIMITED TO, PROCUREMENT OF
     SUBSTITUTE GOODS OR SERVICES; LOSS OF USE, DATA, OR PROFITS; OR BUSINESS
     INTERRUPTION) HOWEVER CAUSED AND ON ANY THEORY OF LIABILITY, WHETHER IN
     CONTRACT, STRICT LIABILITY, OR TORT (INCLUDING NEGLIGENCE OR OTHERWISE)
     ARISING IN ANY WAY OUT OF THE USE OF THIS SOFTWARE, EVEN IF ADVISED OF THE
     POSSIBILITY OF SUCH DAMAGE.

     Redistribution and use in source and binary forms, with or without
     modification, are permitted provided that the following conditions are met:

     * Redistributions of source code must retain the above copyright notice,
     this list of conditions and the above disclaimer.
     * Redistributions in binary form must reproduce the above copyright notice,
     this list of conditions and the above disclaimer in the documentation
     and/or other materials provided with the distribution.
     * Neither the Members of the O-RAN Alliance nor the names of its
     contributors may be used to endorse or promote products derived from
     this software without specific prior written permission.";

  revision 2021-12-01 {
    description
      "version 1.3.0

       1) typographical corrections in descriptions.";
    reference
      "ORAN-WG4.M.0-v01.00";
  }
  revision 2021-03-22 {
    description
      "version 1.2.0

       1) removing non-ASCII characters from model";
    reference
      "ORAN-WG4.M.0-v01.00";
  }
  revision 2019-07-03 {
    description
      "version 1.1.0

       1) corrected error in module reference for LAA feature";
    reference
      "ORAN-WG4.M.0-v01.00";
  }
  revision 2019-02-04 {
    description
      "version 1.0.0

       1) imported model from xRAN
       2) changed namespace and reference from xran to o-ran";
    reference
      "ORAN-WG4.M.0-v01.00";
  }

  typedef band-num {
    type enumeration {
      enum "BAND_46_SUBBAND_A" {
        description
          "46a: 5150 MHz - 5250 MHz";
      }
      enum "BAND_46_SUBBAND_B" {
        description
          "46b: 5250 MHz - 5350 MHz";
      }
      enum "BAND_46_SUBBAND_C" {
        description
          "46c: 5470 MHz - 5725 MHz";
      }
      enum "BAND_46_SUBBAND_D1" {
        description
          "46d1: 5725 MHz - 5850 MHz";
      }
      enum "BAND_46_SUBBAND_D2" {
        description
          "46d2: 5850 MHz - 5925 MHz";
      }
    }
    description
      "This value indicates the list of bands supported as per the document,
       3GPP TS 36.104 V14.2.0 (2016-12), 'Section 5.5 Operation bands'.";
  }

  grouping band-configuration {
    description
      "Grouping for band configuration";
    leaf band-number {
      type band-num;
      description
        "This value indicates the list of bands supported as per the document,
         3GPP TS 36.104 V14.2.0 (2016-12), 'Section 5.5 Operation bands'.";
    }
    leaf-list channel-center-frequency {
      type uint16;
      units "kilohertz";
      description
        "This value indicates carrier centre frequency in KHz";
    }
  }

  grouping measurement-parameters {
    description
      "Grouping for measurement parameters";
    leaf duration-per-channel {
      type uint16;
      units "milliseconds";
      description
        "This value indicates measurement duration per channel in milliseconds.";
    }
    leaf maximum-response-time {
      type uint16;
      units "seconds";
      description
        "This value indicates maximum response time (i.e., timer) in seconds.";
    }
  }

  grouping channel-result-element {
    description
      "Grouping for channel result element";
    leaf measured-channel {
      type uint16;
      units "kilohertz";
      description
        "This value indicates carrier centre frequency for which the result is computed in KHz.";
    }
    leaf occupancy-ratio {
      type uint8;
      units "percent";
      description
        "This value indicates occupancy ratio in percentage.";
    }
    leaf average-rssi {
      type int8;
      units "dBm";
      description
        "This value indicates average RSSI in dBm";
    }
  }

  grouping band-result-element {
    description
      "Grouping for band result element";
    leaf band-number {
      type band-num;
      description
        "This value indicates the band for which the result is computed.";
    }
    leaf measurement-success {
      type boolean;
      description
        "This value indicates whether the measurement is successful for the given band.";
    }
    leaf failure-message {
      when "../measurement-success='false'";
      type enumeration {
        enum "TIMEOUT" {
          description
            "Timed out waiting for measurement completion.";
        }
      }
      description
        "This value indicates the detailed error message for failure of the measurement at O-RU.";
    }
    list channel-result {
      when "../measurement-success='true'";
      key "measured-channel";
      description
        "Results for a particular channel";
      uses channel-result-element;
    }
  }

  rpc start-measurements {
    if-feature "mcap:LAA";
    description
      "Measurements for Carrier-Selection and Dynamic Frequency Selection (DFS)";

    input {
      list band-config {
        key "band-number";
        description
          "Per band configuration for measurements.";
        uses band-configuration;
      }
      uses measurement-parameters;
    }
    output {
      list band-config {
        key "band-number";
        description
          "Output list for all the bands requested for measurements.";
        leaf band-number {
          type band-num;
          description
            "This value indicates the list of bands supported as per the document,
             3GPP TS 36.104 V14.2.0 (2016-12), 'Section 5.5 Operation bands'.";
        }
        leaf-list carrier-center-frequency {
          type uint16;
          units "kilohertz";
          description
            "This value indicates carrier centre frequency in KHz";
        }
        leaf status {
          type enumeration {
            enum "ACCEPTED" {
              description
                "This indicates the measurements for particular sub band is accepted at O-RU.";
            }
            enum "REJECTED" {
              description
                "This indicates the measurements for particular sub band is rejected at O-RU.";
            }
          }
          description
            "This value indicates the status of the measurement acceptance at O-RU.";
        }
        leaf error-message {
          when "../status='REJECTED'";
          type string;
          description
            "This value indicates the detailed error message for the measurement being rejected at O-RU.";
        }
      }
    }
  }

  notification measurement-result {
    if-feature "mcap:LAA";
    description
      "Notification to provide the results of carrier selection and DFS.";
    list band-result {
      key "band-number";
      description
        "Results for a particular sub band under band 46.";
      uses band-result-element;
    }
  }
}
