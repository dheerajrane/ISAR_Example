module o-ran-ieee802-dot1q-cfm {
  yang-version 1.1;
  namespace "urn:o-ran:o-ran-ieee802-dot1q-cfm:1.0";
  prefix o-ran-ieee802-dot1q-cfm;

  import ieee802-dot1q-cfm {
    prefix dot1q-cfm;
  }
  import ietf-interfaces {
    prefix if;
  }
  import o-ran-interfaces {
    prefix o-ran-int;
  }

  organization
    "O-RAN Alliance";
  contact
    "www.o-ran.org";
  description
    "This module defines o-ran augmentations over dot1q.cfm.

     Copyright 2023 the O-RAN Alliance.

     THIS SOFTWARE IS PROVIDED BY THE COPYRIGHT HOLDERS AND CONTRIBUTORS 'AS IS'
     AND ANY EXPRESS OR IMPLIED WARRANTIES, INCLUDING, BUT NOT LIMITED TO, THE
     IMPLIED WARRANTIES OF MERCHANTABILITY AND FITNESS FOR A PARTICULAR PURPOSE
     ARE DISCLAIMED. IN NO EVENT SHALL THE COPYRIGHT HOLDER OR CONTRIBUTORS BE
     LIABLE FOR ANY DIRECT, INDIRECT, INCIDENTAL, SPECIAL, EXEMPLARY, OR
     CONSEQUENTIAL DAMAGES (INCLUDING, BUT NOT LIMITED TO, PROCUREMENT OF
     SUBSTITUTE GOODS OR SERVICES; LOSS OF USE, DATA, OR PROFITS; OR BUSINESS
     INTERRUPTION) HOWEVER CAUSED AND ON ANY THEORY OF LIABILITY, WHETHER IN
     CONTRACT, STRICT LIABILITY, OR TORT (INCLUDING NEGLIGENCE OR OTHERWISE)
     ARISING IN ANY WAY OUT OF THE USE OF THIS SOFTWARE, EVEN IF ADVISED OF THE
     POSSIBILITY OF SUCH DAMAGE.

     Redistribution and use in source and binary forms, with or without
     modification, are permitted provided that the following conditions are met:

     * Redistributions of source code must retain the above copyright notice,
     this list of conditions and the above disclaimer.
     * Redistributions in binary form must reproduce the above copyright notice,
     this list of conditions and the above disclaimer in the documentation
     and/or other materials provided with the distribution.
     * Neither the Members of the O-RAN Alliance nor the names of its
     contributors may be used to endorse or promote products derived from
     this software without specific prior written permission.";

  revision 2023-04-10 {
    description
      "Version 12.0.0
       1)initial version ";
    reference
      "ORAN-WG4.M.0-v12.00";
  }

  augment "/dot1q-cfm:cfm/dot1q-cfm:maintenance-group/dot1q-cfm:mep" {
    description
      "augment mep with vid";
    leaf interface {
      type if:interface-ref;
      description
        "An interface, either a Bridge Port or an aggregated IEEE 802.3 port
         within a Bridge Port, to which the MEP is attached. Each interface in
         the system is uniquely identified by an interface-name. The structure
         and content of the name is outside the scope of this specification.";
      reference
        "[802.1q] 12.14.7.1.3:b";
    }
    leaf primary-vid {
      type leafref {
        path "/if:interfaces/if:interface/o-ran-int:vlan-id";
      }
      description
        "The Primary VID of the MEP. The value 0 indicates that either the
         Primary VID is that of the MEP's MA or that the MEP's MA is
         associated with no VID";
      reference
        "[802.1q] 12.14.7.1.3:d";
    }
  }
}
